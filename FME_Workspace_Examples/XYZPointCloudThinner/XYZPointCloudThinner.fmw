FME workspace XYZPointCloudThinner.fmw

Parameters:
- SourceDataset_POINTCLOUDXYZ = FilePath.xyz   # Point Cloud XYZ File(s)
- DestDataset_POINTCLOUDXYZ = FilePath.xyz   # Destination Point Cloud XYZ Folder

Readers:
- POINTCLOUDXYZ_1: POINTCLOUDXYZ from $(SourceDataset_POINTCLOUDXYZ)

Writers:
- POINTCLOUDXYZ_2: POINTCLOUDXYZ to $(DestDataset_POINTCLOUDXYZ)

POINTCLOUDXYZ (reader POINTCLOUDXYZ_1)
    -> PointCloudThinner
PointCloudThinner
    INTERVAL = 10
    THINNED -> POINTCLOUDXYZ (writer POINTCLOUDXYZ_2)
POINTCLOUDXYZ (writer POINTCLOUDXYZ_2)
